module sfc-pot-netconf-renderer-impl {

  yang-version 1;
  namespace "urn:opendaylight:params:xml:ns:yang:controller:config:sfc-pot-netconf-renderer:impl";
  prefix "sfc-pot-netconf-renderer-impl";

  import config { prefix config; revision-date 2013-04-05; }
  import opendaylight-md-sal-binding { prefix mdsal; revision-date 2013-10-28; }


  description
      "This module contains the base YANG definitions for
      sfc-pot-netconf-renderer Proof of Transit
      renderer implementation.";

  revision "2016-08-30" {
      description
          "Initial revision.";
  }

  // This is the definition of the service implementation as a module identity
  identity sfc-pot-netconf-renderer-impl {
      base config:module-type;

      // Specifies the prefix for generated java classes.
      config:java-name-prefix SfcPotNetconfRenderer;
  }


  // Augments the 'configuration' choice node under modules/module.
  augment "/config:modules/config:module/config:configuration" {
    case sfc-pot-netconf-renderer-impl {
      when "/config:modules/config:module/config:type = 'sfc-pot-netconf-renderer-impl'";

      //wires in the data-broker service
      container data-broker {
        uses config:service-ref {
          refine type {
              mandatory false;
              config:required-identity mdsal:binding-async-data-broker;
          }
        }
      }
      container binding-registry {
        uses config:service-ref {
          refine type {
              mandatory true;
              config:required-identity mdsal:binding-broker-osgi-registry;
          }
        }
      }

      container notification-service {
        uses config:service-ref {
          refine type {
            mandatory true;
            config:required-identity mdsal:binding-notification-service;
          }
        }
      }

      container rpc-registry {
        uses config:service-ref {
          refine type {
             mandatory true;
             config:required-identity mdsal:binding-rpc-registry;
          }
        }
      }
    }
  }
}
