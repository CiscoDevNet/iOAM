module ioam-nb-system {
  yang-version 1;
  namespace "urn:cisco:params:xml:ns:yang:ioam-nb-system";
  prefix ioam-nb-system;

  import network-topology { prefix topo; }

  import ietf-inet-types {
    prefix inet;
  }

  organization "Cisco Systems, Inc.";

  revision 2015-11-22;

  container nb-sys-profiles {
  list nb-sys-profile {
    key "nb-sys-profile-name";
    ordered-by system;
    description
      "Set of system profiles that are defined. ";

    leaf nb-sys-profile-name {
      type string;
      description
        "Unique name associated with this iOAM profile.";
    }

    list classifier-names {
      key "index";
      ordered-by system;
      description
        "Set of classifiers that will identify flows";

      leaf index {
        type uint32;
        mandatory true;
        description
          "Unique identifier for each classifier";
      }

      /*** From ioam-nb-classifier ***/
      leaf classifier-name {
        type string;
        description
          "The classifier name associated with this iOAM profile.";
      }
    }

    list nodes-border {
      key "index";
      ordered-by system;
      description
        "List of border nodes that can do the encap/decap";

      leaf index {
        type uint32;
        mandatory true;
        description
          "Unique identifier for each border node";
      }

      leaf node-id {
        type uint32;
        mandatory true;
        description
          "Node identifier in the system";
      }

      /*** from network-topology, tie up to netconf node id */
      leaf netconf-node {
        type topo:node-ref;
      }
    }

    list nodes-internal {
      key "index";
      ordered-by system;
      description
        "List of internal nodes that can do the updates ";

      leaf index {
        type uint32;
        mandatory true;
        description
          "Unique identifier for each internal node";
      }

      leaf node-id {
        type uint32;
        mandatory true;
        description
          "Node identifier in the system";
      }

      /*** from network-topology, tie up to netconf node id */
      leaf netconf-node {
        type topo:node-ref;
      }
    }

    /*** Data export netflow server and port */
    leaf data-export-nflow-ip {
      type inet:ipv4-address;
      description
        "The netflow server's IPv4 address for data export.";
    }

    leaf data-export-nflow-port {
      type inet:port-number;
      description
        "The netflow server's UDP port for data export.";
    }

    list ioam-profiles {
      key "index";
      ordered-by system;
      description
        "Ordered list of iOAM profiles enabled for this service profile.";

      leaf index {
        type uint16;
      }

      /*** From ioam-nb-pow ***/
      leaf pow-profile-name {
        type string;
        description
          "The Proof of Work profile associated with this iOAM profile";
      }

      /*** From ioam-nb-trace ***/
      leaf trace-profile-name {
        type string;
        description
          "The tracing profile associated with this flow";
      }
    }
/*** list: end ***/
  }
/*** container: end ***/
  }
/*** module: end ***/
}
