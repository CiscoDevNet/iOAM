module ioam-nb-trace {
  yang-version 1;
  namespace "urn:cisco:params:xml:ns:yang:ioam-nb-trace";
  prefix ioam-nb-trace;

  organization "Cisco Systems, Inc.";

  revision 2016-02-02;

  container trace-profiles {

  list trace-profile {
    key "trace-profile-name";
    ordered-by system;
    description
      "Set of tracing profiles that group parameters required to enable iOAM tracing at a service node";

    leaf trace-profile-name {
      type string {
        length "0..255";
      }
      mandatory true;
      description
        "Unique identifier for each tracing profile";
    }

    leaf trace-pow-enable {
      type boolean;
      mandatory true;
      description
        "Whether PoW enabled along with this profile or not";
    }

    leaf trace-ppc-enable {
      type boolean;
      mandatory true;
      description
        "Whether PPC enabled along with this profile or not";
    }

    leaf trace-type {
      /*** none ***/
      /*** Add node_id ***/
      /*** Add node_id, ingress_if, egress_if ***/
      /*** Add node_id, timestamp ***/
      /*** Add node_id, app_data ***/
      /*** Add node_id, app_data, timestamp ***/
      /*** Add node_id, ingress_if, egress_if, app_data, timestamp ***/
      type enumeration {
        enum none {
          value 0;
        }
        enum add-nodeid {
          value 1;
        }
        enum add-nodeid-intf {
          value 7;
        }
        enum add-nodeid-tstamp {
          value 9;
        }
        enum add-nodeid-appdata {
          value 17;
        }
        enum add-nodeid-tstamp-appdata {
          value 25;
        }
        enum add-nodeid-intf-tstamp-appdata {
          value 31;
        }
      }

      mandatory true;
      description
        "Trace type that defines the trace element variant.  Moving from LSB to MSB, each bit represents node_id, ingress_if_id, egress_if_id, timestamp, app_data and others are undefined. Currently, the supported values are 0x03, 0x07, 0x09, 0x11, 0x19 and 0x1f.";

    }

    leaf trace-app-data-type {
        /*** none ***/
        /*** GPS derived lat long ***/
        /*** opaque data ***/
      type enumeration {
        enum none {
          value 0;
        }
        enum latlong {
          value 1;
        }
        enum opaque {
          value 2;
        }
      }

      mandatory true;
      description
        "Application specific data type to be added by the node";
    }

    leaf trace-tstamp-type {
      type enumeration {
        enum shortformat {
          value 0;
        }
        enum longformat {
          value 1;
        }
      }

      mandatory true;
      description
        "Format of timestamp trace data to be added by the node";
    }
/*** list: end ***/
  }
/*** container: end ***/
  }
/*** module: end ***/
}
